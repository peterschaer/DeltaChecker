FME workspace updateGPRLists.fmw

Parameters:
- SourceDataset_ORACLE8I_DB = vek1p   # Source Oracle Non-spatial Service
- DestDataset_CSV = \\geodb.infra.be.ch\freigabe\Anwendungen\DeltaChecker\v10.0.0   # Destination Comma Separated Value (CSV) Directory

Readers:
- ORACLE8I_DB_1: ORACLE8I_DB from $(SourceDataset_ORACLE8I_DB)

Writers:
- CSV_1: CSV to $(DestDataset_CSV)

Note: GEODB_DD.VW_EBENE_ZEITSTAND
GEODB_DD.VW_EBENE_ZEITSTAND (reader ORACLE8I_DB_1)
    attributes: UUID varchar2(36), EZS_OBJECTID number(38,0), STA_OBJECTID number(38,0), DAT_BEZEICHNUNG_FR varchar2(25), DAT_BEZEICHNUNG_DE varchar2(25), DAT_OBJECTID number(38,0), EBE_BEZEICHNUNG_LANG_FR varchar2(250), EBE_BEZEICHNUNG_LANG_DE varchar2(250), EBE_BEZEICHNUNG_MITTEL_FR varchar2(50), EBE_BEZEICHNUNG_MITTEL_DE varchar2(50), EBE_BEZEICHNUNG varchar2(8), EZS_REIHENFOLGE number(4,0), LEG_OBJECTID_FR number(38,0), LEG_OBJECTID_DE number(38,0), EBE_OBJECTID number(38,0), GZS_OBJECTID number(38,0)
    -> AttributeFilter_2
AttributeFilter_2
    ATTR_NAME = DAT_OBJECTID
    ATTR_VALUES = 3,4,5,8
    3 -> AttributeRemover_2
    4 -> AttributeRemover_2
    5 -> AttributeRemover_2
    8 -> AttributeRemover_2
AttributeRemover_2
    REMOVE_ATTRS = DAT_BEZEICHNUNG_DE,DAT_BEZEICHNUNG_FR,DAT_OBJECTID,EBE_BEZEICHNUNG_LANG_DE,EBE_BEZEICHNUNG_LANG_FR,EBE_BEZEICHNUNG_MITTEL_DE,EBE_BEZEICHNUNG_MITTEL_FR,EBE_OBJECTID,EZS_REIHENFOLGE,LEG_OBJECTID_DE,LEG_OBJECTID_FR,STA_OBJECTID,UUID
    -> FeatureMerger [input 1]
Note: GEODB_DD.VW_GEOPRODUKT_ZEITSTAND
GEODB_DD.VW_GEOPRODUKT_ZEITSTAND (reader ORACLE8I_DB_1)
    attributes: GZS_OBJECTID number(38,0), UUID varchar2(36), STA_BEZEICHNUNG_FR varchar2(25), STA_BEZEICHNUNG_DE varchar2(25), GPR_DEAKTIVIERT number(4,0), GPR_BEZEICHNUNG_MITTEL_FR varchar2(50), GPR_BEZEICHNUNG_MITTEL_DE varchar2(50), GPR_BEZEICHNUNG varchar2(8), GPR_OBJECTID number(38,0), GZS_URL_IMPORTVERZEICHNIS varchar2(255), GZS_KLASSIFIKATION number(4,0), GZS_VERSION number(38,0), GZS_JAHR number(38,0), GZS_ZEITSTAND date, STA_OBJECTID number(38,0), GZS_AKTUELL number(38,0)
    -> AttributeFilter
AttributeFilter
    ATTR_NAME = GZS_AKTUELL
    ATTR_VALUES = 1
    1 -> AttributeRemover
AttributeRemover
    REMOVE_ATTRS = GPR_BEZEICHNUNG_MITTEL_DE,GPR_BEZEICHNUNG_MITTEL_FR,GPR_DEAKTIVIERT,GPR_OBJECTID,GZS_AKTUELL,GZS_JAHR,GZS_KLASSIFIKATION,GZS_URL_IMPORTVERZEICHNIS,GZS_VERSION,GZS_ZEITSTAND,STA_BEZEICHNUNG_DE,STA_BEZEICHNUNG_FR,STA_OBJECTID,UUID
    -> FeatureMerger [input 2]
    -> Sorter
Sorter
    SORT_PARM = GPR_BEZEICHNUNG ALPHA ASCENDING
    SORTED -> Geoprodukte.csv (writer CSV_1)
Geoprodukte.csv (writer CSV_1)
    attributes: GPR_BEZEICHNUNG char(8)
FeatureMerger
    REFEEATTR = GZS_OBJECTID
    MERGE_TYPE = Attributes Only
    PROCESS_DUPS = No
    BUILD_INCOMPLETE = No
    REFERATTR = GZS_OBJECTID
    COMPLETE -> FeatureHolder
    COMPLETE -> FeatureMerger_2 [input 2]
Note: GEODB_DD.TB_WERTETABELLE
GEODB_DD.TB_WERTETABELLE (reader ORACLE8I_DB_1)
    attributes: WTB_OBJECTID number(38,0), EZS_OBJECTID number(38,0), WTB_BEZEICHNUNG varchar2(8), WTB_BEZEICHNUNG_MITTEL_DE varchar2(50), WTB_BEZEICHNUNG_MITTEL_FR varchar2(50), IMP_OBJECTID number(38,0), WTB_JOIN_FOREIGNKEY varchar2(50), WTB_JOIN_PRIMARYKEY varchar2(25), WTB_JOIN_TYP varchar2(20), WTB_AUTOLOAD number(4,0), WTB_IMPORTNAME varchar2(100)
    -> AttributeRemover_3
AttributeRemover_3
    REMOVE_ATTRS = IMP_OBJECTID,WTB_AUTOLOAD,WTB_BEZEICHNUNG_MITTEL_DE,WTB_BEZEICHNUNG_MITTEL_FR,WTB_IMPORTNAME,WTB_JOIN_FOREIGNKEY,WTB_JOIN_PRIMARYKEY,WTB_JOIN_TYP,WTB_OBJECTID
    -> FeatureMerger_2 [input 1]
FeatureMerger_2
    REFEEATTR = EZS_OBJECTID
    MERGE_TYPE = Attributes Only
    PROCESS_DUPS = No
    BUILD_INCOMPLETE = No
    REFERATTR = EZS_OBJECTID
    COMPLETE -> AttributeRemover_4
AttributeRemover_4
    REMOVE_ATTRS = EBE_BEZEICHNUNG,EZS_OBJECTID,GZS_OBJECTID
    -> StringConcatenator
StringConcatenator
    PARM_LINE = &GPR_BEZEICHNUNG,&WTB_BEZEICHNUNG
    VAL_ATTR = _WERTETABELLE
    -> DuplicateRemover
DuplicateRemover
    KEYATTR = _WERTETABELLE
    UNIQUE -> AttributeRenamer
    DUPLICATE -> Sorter_3
AttributeRenamer
    ATTR_LIST = EBE_BEZEICHNUNG,WTB_BEZEICHNUNG
    -> FeatureHolder
FeatureHolder
    -> Sorter_2
Sorter_2
    SORT_PARM = GPR_BEZEICHNUNG ALPHA ASCENDING EBE_BEZEICHNUNG ALPHA ASCENDING
    SORTED -> Ebenen.csv (writer CSV_1)
Ebenen.csv (writer CSV_1)
    attributes: GPR_BEZEICHNUNG char(8), EBE_BEZEICHNUNG char(8)
Sorter_3
    SORT_PARM = GPR_BEZEICHNUNG ALPHA ASCENDING WTB_BEZEICHNUNG ALPHA ASCENDING
    SORTED -> wt.csv (writer CSV_1)
wt.csv (writer CSV_1) [off]
    attributes: GPR_BEZEICHNUNG char(8), EBE_BEZEICHNUNG char(8)
